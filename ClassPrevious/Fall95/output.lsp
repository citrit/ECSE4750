(defun makepts(filename / ofp ptlist cnt pt1)
  (setq ofp (open filename "a") cnt 0)
  (while (setq pt1 (getpoint "\nPoints: "))
    (setq ptlist (cons pt1 ptlist))
    )
  (princ (strcat "\n0   " (itoa (length ptlist)) "  1.0 1.0 1.0\n") ofp)
  (setq ptlist (reverse ptlist))
  (while (setq pt1 (nth cnt ptlist))
    (princ (car pt1) ofp)(princ " " ofp)
    (princ (cadr pt1) ofp)(princ " " ofp)
    (princ (caddr pt1) ofp)(princ "    " ofp)
    (setq cnt (+ cnt 1))
    )
  (close ofp)
)
(defun makepoints(filename / ofp ptlist cnt pt1)
  (setq ofp (open filename "a") cnt 0)
  (while (setq pt1 (getint "\nConnection Number: "))
    (setq ptlist (cons pt1 ptlist))
    )
  (princ (strcat "\n1   " (itoa (length ptlist)) "  1.0 0.0 0.0\n") ofp)
  (setq ptlist (reverse ptlist))
  (while (setq pt1 (nth cnt ptlist))
    (princ (strcat (itoa pt1) " ") ofp)
    (setq cnt (+ cnt 1))
    )
  (close ofp)
) 

(defun makeline(filename / ofp ptlist cnt pt1)
  (setq ofp (open filename "a") cnt 0)
  (while (setq pt1 (getint "\nStart: "))
    (setq ptlist (cons pt1 ptlist))
    (setq pt1 (getint "\nEnd: "))
    (setq ptlist (cons pt1 ptlist))
    )
  (princ (strcat "\n2   " (itoa (/ (length ptlist) 2)) "  1.0 1.0 0.0\n") ofp)
  (setq ptlist (reverse ptlist))
  (while (setq pt1 (nth cnt ptlist))
    (princ (strcat (itoa pt1) " ") ofp)
    (princ (strcat " " (itoa (nth (+ 1 cnt) ptlist)) "    ") ofp)
    (setq cnt (+ cnt 2))
    )
  (close ofp)
) 

(defun makepolygon(filename / ofp ptlist cnt pt1)
  (setq ofp (open filename "a") cnt 0)
  (while (setq pt1 (getint "\nStart: "))
    (setq ptlist (cons pt1 ptlist))
    )
  (princ (strcat "\n3   1  0.0 1.0 1.0\n") ofp)
  (setq ptlist (reverse ptlist))
  (while (setq pt1 (nth cnt ptlist))
    (princ (strcat (itoa pt1) " ") ofp)
    (setq cnt (+ cnt 1))
    )
  (princ "-1" ofp)
  (close ofp)
) 
(defun makepolyline(filename / ofp ptlist cnt pt1)
  (setq ofp (open filename "a") cnt 0)
  (while (setq pt1 (getint "\nStart: "))
    (setq ptlist (cons pt1 ptlist))
    )
  (princ (strcat "\n5   1  0.0 0.0 1.0\n") ofp)
  (setq ptlist (reverse ptlist))
  (while (setq pt1 (nth cnt ptlist))
    (princ (strcat (itoa pt1) " ") ofp)
    (setq cnt (+ cnt 1))
    )
  (princ "-1" ofp)
  (close ofp)
) 

(defun maketrian(filename / ofp ptlist cnt pt1)
  (setq ofp (open filename "a") cnt 0)
  (while (setq pt1 (getint "\nStart: "))
    (setq ptlist (cons pt1 ptlist))
    (setq pt1 (getstring "\nMiddle: "))
    (setq ptlist (cons pt1 ptlist))
    (setq pt1 (getstring "\nEnd: "))
    (setq ptlist (cons pt1 ptlist))
    )
  (setq ptlist (reverse ptlist))
  (princ (strcat "\n4   " (itoa (/ (length ptlist) 3)) "  0.0 1.0 1.0\n") ofp)
  (while (setq pt1 (nth cnt ptlist))
    (princ (itoa pt1) ofp)
    (princ (strcat " " (nth (+ 1 cnt) ptlist)) ofp)
    (princ (strcat " " (nth (+ 2 cnt) ptlist) "    ") ofp)
    (setq cnt (+ cnt 3))
    )
  (close ofp)
)
